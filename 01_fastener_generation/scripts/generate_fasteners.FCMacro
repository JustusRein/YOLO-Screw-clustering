# -*- coding: utf-8 -*-
"""
FreeCAD Fastener Generator
Generates STL, STEP and FCStd files from fasteners.csv.

Expected CSV columns:
    id, fastener_type, diameter

Optional columns:
    length_mm, part_category, part_type, screw_type,
    thread_type, tool_size, thread_size, thread_pitch,
    screw_length
"""

import FreeCAD as App
import Part
import Mesh
import csv
import os
import traceback
import re
import sys
import time

import FastenersCmd


# ============================================================
# CONFIGURATION
# ============================================================

INPUT_CSV = "/data/input/fasteners.csv"
OUTPUT_DIR = "/data/output"

STL_DIR = os.path.join(OUTPUT_DIR, "stl")
STEP_DIR = os.path.join(OUTPUT_DIR, "step")
FCSTD_DIR = os.path.join(OUTPUT_DIR, "fcstd")

METADATA_FILE = os.path.join(OUTPUT_DIR, "generated_metadata.csv")
LOG_FILE = os.path.join(OUTPUT_DIR, "generation_log.txt")

THREAD_ENABLED = False

EXPORT_STL = True
EXPORT_STEP = True
SAVE_FCSTD = True

# FreeCAD recomputation timeout is not implemented here.
# All geometry operations are performed sequentially.


# ============================================================
# SUPPORTED FASTENER TYPES
# ============================================================

SUPPORTED_TYPES = {
    "ISO4017": "screw",
    "ISO4762": "screw",
    "ISO7046": "screw",
    "ISO7045": "screw",

    "ISO4032": "nut",
    "DIN985": "nut",
    "DIN315": "nut",

    "ISO7089": "washer",
    "ISO7092": "washer",
    "ISO7093-1": "washer",
}

METADATA_FIELDS = [
    "id",
    "filename",
    "stl_file",
    "part_category",
    "part_type",
    "standard",
    "fastener_type",
    "screw_type",
    "diameter",
    "length_mm",
    "thread_type",
    "tool_size",
    "thread_size",
    "thread_pitch",
    "screw_length",
    "generation_status",
]


# ============================================================
# INITIALIZATION
# ============================================================

for directory in (OUTPUT_DIR, STL_DIR, STEP_DIR, FCSTD_DIR):
    os.makedirs(directory, exist_ok=True)

# Start a fresh log for each run.
with open(LOG_FILE, "w", encoding="utf-8") as handle:
    handle.write("FreeCAD Fastener Generator\n")


# ============================================================
# LOGGING
# ============================================================

def log(message):
    message = str(message)
    print("[FASTENER-GENERATOR] " + message, flush=True)

    with open(LOG_FILE, "a", encoding="utf-8") as file:
        file.write(message + "\n")
        file.flush()


# ============================================================
# HELPERS
# ============================================================

def safe_filename(value):
    value = str(value).strip()
    value = re.sub(r"[^a-zA-Z0-9_.-]+", "_", value)
    return value.strip("._") or "unnamed"


def get_value(row, key, default=""):
    value = row.get(key, default)
    if value is None:
        return default
    value = str(value).strip()
    return value if value else default


def validate_file(path, description):
    if not os.path.isfile(path):
        raise RuntimeError("{} was not created: {}".format(description, path))

    if os.path.getsize(path) <= 0:
        raise RuntimeError("{} is empty: {}".format(description, path))


def read_csv():
    if not os.path.isfile(INPUT_CSV):
        raise FileNotFoundError("Input CSV not found: " + INPUT_CSV)

    with open(INPUT_CSV, "r", encoding="utf-8-sig", newline="") as handle:
        reader = csv.DictReader(handle)

        if not reader.fieldnames:
            raise ValueError("CSV has no header row.")

        required = {"id", "fastener_type", "diameter"}
        missing = required.difference(reader.fieldnames)

        if missing:
            raise ValueError(
                "Missing required CSV columns: {}".format(
                    ", ".join(sorted(missing))
                )
            )

        rows = list(reader)

    if not rows:
        raise ValueError("CSV contains no fastener entries.")

    return rows


def get_fastener_category(row):
    category = get_value(row, "part_category").lower()

    if category:
        return category

    fastener_type = get_value(row, "fastener_type")
    return SUPPORTED_TYPES.get(fastener_type, "unknown")


def get_part_type(row):
    part_type = get_value(row, "part_type")

    if part_type:
        return part_type

    return safe_filename(
        get_value(row, "screw_type", "unknown")
    ).lower()


def get_enumeration_values(obj, property_name):
    try:
        values = obj.getEnumerationsOfProperty(property_name)
        return list(values or [])
    except Exception:
        return []


def set_diameter(obj, requested_diameter):
    requested = str(requested_diameter).strip()
    available = get_enumeration_values(obj, "Diameter")

    if not available:
        raise RuntimeError(
            "Fasteners object has no available Diameter enumeration."
        )

    # Prefer exact match. Also allow a normalized numeric match:
    # e.g. CSV "6" against a Workbench value "6mm".
    candidates = [requested]

    numeric_match = re.match(r"^M?\s*(\d+(?:[.,]\d+)?)\s*mm?$", requested, re.I)
    if numeric_match:
        number = numeric_match.group(1).replace(",", ".")
        candidates.extend([number, "M" + number, number + "mm"])

    selected = None

    for candidate in candidates:
        if candidate in available:
            selected = candidate
            break

    if selected is None:
        raise ValueError(
            "Unsupported diameter '{}'. Available values: {}".format(
                requested, available
            )
        )

    obj.Diameter = selected


def set_length(obj, requested_length):
    if not hasattr(obj, "Length"):
        return

    requested = str(requested_length).strip()

    if not requested:
        raise ValueError("Length is required for this fastener.")

    available = get_enumeration_values(obj, "Length")

    if requested in available:
        obj.Length = requested
        return

    # Some Fasteners Workbench objects expose a Custom length.
    if "Custom" in available and hasattr(obj, "LengthCustom"):
        try:
            obj.Length = "Custom"
            obj.LengthCustom = App.Units.Quantity(requested + " mm")
            return
        except Exception as exc:
            raise ValueError(
                "Could not set custom length '{}': {}".format(requested, exc)
            )

    raise ValueError(
        "Unsupported length '{}'. Available values: {}".format(
            requested, available
        )
    )


def check_shape(obj):
    if not hasattr(obj, "Shape"):
        raise RuntimeError("Generated object has no Shape property.")

    shape = obj.Shape

    if shape is None or shape.isNull():
        raise RuntimeError("Generated shape is empty.")

    if not shape.isValid():
        raise RuntimeError("Generated shape is invalid.")

    if len(shape.Solids) == 0:
        raise RuntimeError("Generated shape contains no solids.")


def metadata_base(row):
    fastener_type = get_value(row, "fastener_type")
    return {
        "id": get_value(row, "id"),
        "filename": "",
        "stl_file": "",
        "part_category": get_fastener_category(row),
        "part_type": get_part_type(row),
        "standard": get_value(row, "standard", fastener_type),
        "fastener_type": fastener_type,
        "screw_type": get_value(row, "screw_type", get_part_type(row)),
        "diameter": get_value(row, "diameter"),
        "length_mm": get_value(row, "length_mm"),
        "thread_type": get_value(row, "thread_type", "simple"),
        "tool_size": get_value(row, "tool_size"),
        "thread_size": get_value(row, "thread_size", get_value(row, "diameter")),
        "thread_pitch": get_value(row, "thread_pitch"),
        "screw_length": get_value(row, "screw_length"),
        "generation_status": "failed",
    }


# ============================================================
# FASTENER CREATION
# ============================================================

def create_fastener(row):
    metadata = metadata_base(row)

    fastener_id = metadata["id"]
    fastener_type = metadata["fastener_type"]
    category = metadata["part_category"]
    diameter = metadata["diameter"]
    length = metadata["length_mm"]
    part_type = metadata["part_type"]

    if fastener_type not in SUPPORTED_TYPES:
        raise ValueError("Unsupported fastener type: " + fastener_type)

    expected_category = SUPPORTED_TYPES[fastener_type]

    if category != expected_category:
        raise ValueError(
            "{} is registered as '{}', not '{}'.".format(
                fastener_type, expected_category, category
            )
        )

    if category not in ("screw", "nut", "washer"):
        raise ValueError("Unsupported category: " + category)

    if not diameter:
        raise ValueError("Diameter is missing.")

    name = safe_filename(
        "{}_{}_{}_{}".format(
            fastener_id, fastener_type, part_type, diameter
        )
        + ("_L" + length if length else "")
    )

    log("")
    log("=" * 60)
    log("Generating: " + name)
    log("Category: " + category)
    log("Standard: " + fastener_type)
    log("Diameter: " + diameter)
    log("Length: " + (length or "N/A"))

    doc = None

    try:
        doc = App.newDocument(name)

        obj = doc.addObject("Part::FeaturePython", "Fastener")

        # The Fasteners Workbench constructor is version-dependent.
        # This is the constructor used by the original project.
        FastenersCmd.FSScrewObject(obj, fastener_type, None)

        set_diameter(obj, diameter)

        if category == "screw":
            set_length(obj, length)

        if hasattr(obj, "Thread"):
            obj.Thread = THREAD_ENABLED

        obj.Label = name

        doc.recompute()
        check_shape(obj)

        # Export STL
        stl_filename = name + ".stl"
        stl_path = os.path.join(STL_DIR, stl_filename)

        if EXPORT_STL:
            Mesh.export([obj], stl_path)
            validate_file(stl_path, "STL")

            metadata["filename"] = stl_filename
            metadata["stl_file"] = stl_filename
            log("STL exported: " + stl_path)

        # Export STEP
        step_path = os.path.join(STEP_DIR, name + ".step")

        if EXPORT_STEP:
            Part.export([obj], step_path)
            validate_file(step_path, "STEP")
            log("STEP exported: " + step_path)

        # Save FreeCAD document
        fcstd_path = os.path.join(FCSTD_DIR, name + ".FCStd")

        if SAVE_FCSTD:
            doc.recompute()
            doc.saveAs(fcstd_path)
            validate_file(fcstd_path, "FCStd")
            log("FCStd saved: " + fcstd_path)

        metadata["generation_status"] = "success"
        return metadata

    finally:
        if doc is not None:
            try:
                App.closeDocument(doc.Name)
            except Exception as exc:
                log("WARNING: Could not close document: {}".format(exc))


# ============================================================
# METADATA OUTPUT
# ============================================================

def write_metadata(rows):
    temp_path = METADATA_FILE + ".tmp"

    with open(temp_path, "w", encoding="utf-8-sig", newline="") as handle:
        writer = csv.DictWriter(
            handle,
            fieldnames=METADATA_FIELDS,
            extrasaction="ignore"
        )
        writer.writeheader()
        writer.writerows(rows)

    os.replace(temp_path, METADATA_FILE)


# ============================================================
# MAIN
# ============================================================

def main():
    log("")
    log("=" * 60)
    log("FREECAD FASTENER GENERATOR")
    log("FreeCAD version: {}".format(App.Version()))
    log("FastenersCmd: {}".format(getattr(FastenersCmd, "__file__", "unknown")))
    log("=" * 60)

    rows = read_csv()
    log("Input entries: {}".format(len(rows)))

    metadata_rows = []
    successful = 0
    failed = 0

    for index, row in enumerate(rows, start=1):
        log("Processing entry {}/{}".format(index, len(rows)))

        try:
            metadata = create_fastener(row)
            metadata_rows.append(metadata)
            successful += 1
            log("SUCCESS: {}".format(metadata["filename"]))

        except Exception as error:
            failed += 1
            metadata = metadata_base(row)
            metadata_rows.append(metadata)

            log("ERROR for ID {}: {}".format(metadata["id"], error))
            log(traceback.format_exc())

    write_metadata(metadata_rows)

    log("")
    log("=" * 60)
    log("GENERATION FINISHED")
    log("Successful: {}".format(successful))
    log("Failed: {}".format(failed))
    log("Total: {}".format(len(rows)))
    log("Metadata: {}".format(METADATA_FILE))
    log("=" * 60)

    # Return a failing exit code so Docker and the pipeline can detect errors.
    if failed:
        log("One or more fasteners failed. Exiting with error.")
        raise RuntimeError(
            "{} of {} fasteners failed.".format(failed, len(rows))
        )


# ============================================================
# RUN
# ============================================================

if __name__ == "__main__":
    try:
        main()
    except Exception as e:
        log(f"FATAL ERROR: {e}")
        traceback.print_exc()
        raise
    finally:
        log("Closing FreeCAD...")

        try:
            import FreeCADGui as Gui
            Gui.getMainWindow().close()
        except Exception:
            pass
